module access {
    namespace "http://com/example/access";
    prefix access;

    import ietf-inet-types { prefix inet; }
    import tailf-ncs { prefix ncs; }

    list access {
        key customer;

        uses ncs:service-data;
        ncs:servicepoint "access";

        leaf customer {
            type string;
        }

        leaf device {
            mandatory true;
            type leafref {
                path "/ncs:devices/ncs:device/ncs:name";
            }
        }

        leaf vlan {
            mandatory true;
            type uint16;
        }

        leaf access-ge-interface {
            mandatory true;
            type string;
        }

        leaf trunk-ge-interface {
            mandatory true;
            type string;
        }
    }
}
