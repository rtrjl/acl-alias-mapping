module cliparser-extensions-v11 {
  // Generated by yanger -t ncs
  tailf:ncs-device-type "cli-ned";

  namespace "http://tail-f.com/ned/cliparser_v11";
  prefix cli;

  import tailf-ncs {
    prefix ncs;
  }
  import tailf-common {
    prefix tailf;
  }

  extension globally-unique-value {
    cli:direction "to-device";
    cli:state "post-match";
    cli:java-callback-method "com.tailf.packages.ned.nedcom.NedComCliExtensions.globallyUniqueValue";
    argument value;
  }

  extension shutdown-before-edit {
    cli:direction "to-device";
    cli:state "post-match";
    cli:java-callback-method "com.tailf.packages.ned.nedcom.NedComCliExtensions.shutdownBeforeEdit";
    argument value;
  }

  extension context-value-inject {
    cli:direction "from-device";
    cli:state "enter-context";
    cli:java-callback-method "com.tailf.packages.ned.nedcom.NedComCliExtensions.contextValueInject";
    argument value;
  }

  extension parse-no-auto-match {
    cli:builtin "true";
  }

  extension parse-alt-name {
    cli:builtin "true";
    argument value;
  }

  extension parse-inline-when {
    cli:builtin "true";
  }

  extension parse-global-when {
    cli:builtin "true";
  }

  extension parse-relaxed-syntax {
    cli:builtin "true";
  }

  extension parse-compact-syntax {
    cli:builtin "true";
  }

  extension java-callback-method {
    cli:builtin "true";
    argument value;
  }

  extension module-meta-data {
    cli:builtin "true";
  }

  extension callback {
    cli:builtin "true";
    argument value;
  }

  extension arguments {
    cli:builtin "true";
    argument value;
  }

  extension state {
    cli:builtin "true";
    argument value;
  }

  extension direction {
    cli:builtin "true";
    argument value;
  }

  extension builtin {
    argument value;
    cli:builtin "true";
  }
}
