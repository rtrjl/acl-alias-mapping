module access-python {

  namespace "http://example.com/access-python";
  prefix access-python;

  import ietf-inet-types {
    prefix inet;
  }
  import tailf-common {
    prefix tailf;
  }
  import tailf-ncs {
    prefix ncs;
  }

  description
    "Bla bla...";

  revision 2016-01-01 {
    description
      "Initial revision.";
  }

  list access-python {
    description "This is an RFS skeleton service";

    key customer;
    leaf customer {
        type string;
    }

    uses ncs:service-data;
    ncs:servicepoint access-python-servicepoint;

    // may replace this with other ways of refering to the devices.
    leaf device {
        mandatory true;
        type leafref {
        path "/ncs:devices/ncs:device/ncs:name";
        }
    }

    leaf access-ge-interface {
       mandatory true;
       type string;
       }

    leaf trunk-ge-interface {
        mandatory true;
        type string;
        }

    leaf vlan {
        config false;
            tailf:cdb-oper {
            tailf:persistent true;
        }
        type uint16;
    }
  }
}
